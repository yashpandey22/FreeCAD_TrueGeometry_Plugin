import os
import tempfile
import platform
import sys
import Mesh
from threading import Thread
from tkinter import messagebox
from tkinter.ttk import Progressbar
import tkinter as tk
from tkinter import ttk


###Library check
try:
    import requests as rs
except ImportError:
    import subprocess
    if platform.system() == 'Windows':
        subprocess.check_call(['python', '-m', 'pip', 'install', 'requests'])
    else:
        subprocess.check_call(['python3', '-m', 'pip', 'install', 'requests'])
finally:
    import requests as rs


###Design of GUI

window = tk.Tk()
window.title("TrueGeometry FreeCAD Plugin")
window.geometry("650x600")
tabControl = ttk.Notebook(window)

tab1 = ttk.Frame(tabControl)
tab2 = ttk.Frame(tabControl)
tab3 = ttk.Frame(tabControl)

tabControl.add(tab1, text = "Upload")
tabControl.add(tab2, text = "Download")
tabControl.add(tab3, text = "Crossover Download")
tabControl.pack(expand = 1, fill = "both")


###---------------------------------------------------------------------------------------------------------------------------------------------
###Upload function TAB1
def Upload():
    
    def Progress_Bar_th():
        import time
        while(1):                
            Progress_Bar_Upload['value'] = 20
            window.update_idletasks()
            time.sleep(1)

            Progress_Bar_Upload['value'] = 40
            window.update_idletasks()
            time.sleep(1)

            Progress_Bar_Upload['value'] = 60
            window.update_idletasks()
            time.sleep(1)
            
            Progress_Bar_Upload['value'] = 80
            window.update_idletasks()
            time.sleep(1)
            
            Progress_Bar_Upload['value'] = 100
            window.update_idletasks()
            time.sleep(1)
            
            Progress_Bar_Upload['value'] = 80
            window.update_idletasks()
            time.sleep(1)
            
            Progress_Bar_Upload['value'] = 60
            window.update_idletasks()
            time.sleep(1)
            
            Progress_Bar_Upload['value'] = 40
            window.update_idletasks()
            time.sleep(1)
            
            Progress_Bar_Upload['value'] = 20
            window.update_idletasks()
            time.sleep(1)
            
            Progress_Bar_Upload['value'] = 0
            window.update_idletasks()
            time.sleep(1)          
    
    def Upload_th():

        P1 = Thread(target = Progress_Bar_th, daemon = True).start()#starting the Progress Bar Thread

        ###Exporting to Object File
        file_name = App.ActiveDocument.Name
        Format = Format_Gui.get()
        path_file = tempfile.gettempdir()

        if Format == "FreeCAD Standard(.FCStd)": #For Uploading as a FreeCAD Standard Format (.FCStd)
            path_file = path_file + "/" + file_name + ".FCStd"
            App.getDocument(file_name).saveCopy(path_file)
        
        else:
            path_file = path_file + "/" + file_name + ".obj" #Path and Name of File to be exported 
            __objs__ = [] #Empty List to appending document details and all object names
            for obj in FreeCAD.ActiveDocument.Objects: #Loop for appending all the object names as string to a list
                if obj.ViewObject.isVisible():
                    __objs__.append(FreeCAD.getDocument(file_name).getObject(obj.Name)) #List with appended document details and all object names
            import Mesh
            Mesh.export(__objs__, path_file)#File Exported to object file (.obj)
            del __objs__

        ###Commands for Uploading to TrueGeometry.com
        API_Key = API_Key_Upload.get() #Permanent API Key
        url = ("http://www.truegeometry.com") #Website's URL
        r = rs.get("http://www.truegeometry.com/getUpldToken?APIKey=" + API_Key) #Temporary API Key Recieved
        Temp_APIKEY = r.json()['apiKeyToken'] #Temporary API Key
        to_Upload = {'media': open(path_file, 'rb')} #path of recently exported file
        GeometryClass = GeometryClass_Gui.get() #Getting Geometry Class
        Tags = Tags_Gui.get() #Getting Tags
        Upload_file = rs.post(url + "/upldAPI?APIKey=" + API_Key + "&APIKeyToken=" + Temp_APIKEY + "&tags=" + Tags + "&GeometryClass=" + GeometryClass, files = to_Upload)
        #File Upload command through HTTP Post using Requests Library.
        
        if Upload_file.text == 'success' : #Message to User Upload Successfull or Unsuccessful
            messagebox.showinfo("TrueGeometry", "Upload Completed Successfully!")
            window.destroy()         

        else:
            messagebox.showinfo("TrueGeometry", "Something Went Wrong, Please Try Again!")
            window.destroy()

        os.remove(path_file) #Removing the Created Object File from users Computer    
        P2.exit()        
    
    P2 = Thread(target = Upload_th, daemon = True).start()
    

###---------------------------------------------------------------------------------------------------------------------------------------------
###Download function TAB2
def Download():

    ###File Download Code
    API_Key = API_Key_Download.get()
    API_FileName = API_FileName_Gui.get()
    r = rs.get("http://www.truegeometry.com/api/get3DAsm?modelName=" + API_FileName + "&APIKey=" + API_Key)

    response_get = r.text
    response_get = response_get[response_get.find(":") + 2 : response_get.find("}")]
    count = response_get.count(':')
    path = tempfile.gettempdir()

    ###Creating a New File in FreeCAD
    App.newDocument("Unnamed")
    App.setActiveDocument("Unnamed")
    App.ActiveDocument = App.getDocument("Unnamed")
    Gui.ActiveDocument = Gui.getDocument("Unnamed")
    Gui.activeDocument().activeView().viewDefaultOrientation()

    ###Looping through all the parts in a 3D model and importing to FreeCAD
    for i in range(count):
        progress = int(i) * 7
        Progress_Bar_Download['value'] = progress
         
        part_name = response_get[response_get.find("\"") + 1 : response_get.find(":") - 1]
        a = response_get = response_get[response_get.find(":") + 2 : ]
        a = response_get[: response_get.find("\"")]
        response_get = response_get[response_get.find(",") : ]    
        part = rs.get("http://www.truegeometry.com" + a + "&APIKey=" + API_Key)
        filename_downloaded = path + "/" + part_name + ".obj"
        open(filename_downloaded, 'wb').write(part.content)
        Mesh.insert(filename_downloaded, "Unnamed")
        Gui.SendMsgToActiveView("ViewFit")
        window.update_idletasks()

    messagebox.showinfo("TrueGeometry", "Download Completed Successfully!")
    window.destroy()
    

###---------------------------------------------------------------------------------------------------------------------------------------------
###Crossover Function TAB3
def Crossover():
    ###Basic Details
    API_Key = API_Key_Crossover.get()
    M1 = API_PrimaryName_Gui.get()
    M2 = API_SecondaryName_Gui.get()
    r = rs.get("http://www.truegeometry.com/api/transform/model3D?m1=" + M1 + "&m2=" + M2 + "&APIKey=" + API_Key)
    response_get = r.text
    count = response_get.count(':')
    path = tempfile.gettempdir()

    ###Creating a New File in FreeCAD
    App.newDocument("Unnamed")
    App.setActiveDocument("Unnamed")
    App.ActiveDocument = App.getDocument("Unnamed")
    Gui.ActiveDocument = Gui.getDocument("Unnamed")
    Gui.activeDocument().activeView().viewDefaultOrientation()

    for i in range(count):
        progress = int(i)
        Progress_Bar_Crossover['value'] = progress
        part_name = response_get[response_get.find("\"") + 1 : response_get.find(":") - 1]
        a = response_get = response_get[response_get.find(":") + 2 : ]
        a = response_get[: response_get.find("\"")]
        response_get = response_get[response_get.find(",") : ]
        part = rs.get("http://www.truegeometry.com" + a + "&APIKey=" + API_Key)
        filename_downloaded = path + "/" + part_name + ".obj"
        open(filename_downloaded, 'wb').write(part.content)
        Mesh.insert(filename_downloaded, "Unnamed")
        Gui.SendMsgToActiveView("ViewFit")
        window.update_idletasks()
        
        
    messagebox.showinfo("TrueGeometry", "Crossover Download Completed Successfully!")
    window.destroy()
    

###---------------------------------------------------------------------------------------------------------------------------------------------
###Upload Function TAB1

###Information for user 
Text_Label_Upload = tk.Label(tab1, text = "Welcome to TrueGeometry Uplaod \n Get your Permanent API Key from Profile Page by \n Updagting your Profile @ www.truegeometry.com").grid(row = 0, column = 1, padx = 10, pady = 25)

### API Key Field
API_Key_Upload = tk.StringVar() #Variable declaration to get API Key input
API_Key_Label_Upload = tk.Label(tab1, text = "Enter API Key").grid(row = 1, padx = 10, pady = 25) 
API_Key_Entry_Upload = tk.Entry(tab1, textvariable = API_Key_Upload).grid(row = 1, column = 1)

### Select Geommetry Class Drop Down Menu 
ttk.Label(tab1, text = "Select Geometry Class").grid(row = 2, column = 0, padx = 10, pady = 25)
GeometryClass_Gui = tk.StringVar()
GeometryClassChoose = ttk.Combobox(tab1, width = 27, textvariable = GeometryClass_Gui)
GeometryClassChoose['values'] = ('Buildings',  
                          'Mega Structures', 
                          'Vehicles', 
                          'Ships', 
                          'Characters', 
                          'Aircraft', 
                          'Furniture', 
                          'Electronics', 
                          'Animals', 
                          'Plants', 
                          'Weapons', 
                          'Sports'
                          'Food',
                          'Anatomy',
                          'Topology',
                          'Outer Space',
                          'Others') 

GeometryClassChoose.grid(column = 1, row = 2)
GeometryClassChoose.current()

###Enter Tags
Tags_Gui = tk.StringVar() #Variable declaration to get Tags input
Tag_Lable = tk.Label(tab1, text = "Enter Tags").grid(row = 3, padx = 10, pady = 25)
Tags_Entry = tk.Entry(tab1, textvariable = Tags_Gui).grid(row = 3, column = 1)

###Enter File Format .FCStd or .Obj
ttk.Label(tab1, text = "Select File Format").grid(row = 4, column = 0, padx = 10, pady = 25)
Format_Gui = tk.StringVar()
FormatChosen = ttk.Combobox(tab1, width = 27, textvariable = Format_Gui)
FormatChosen['values'] = ('FreeCAD Standard(.FCStd)',  
                          'Object File(.obj)') 

FormatChosen.grid(column = 1, row = 4)
FormatChosen.current()

###Progress Bar
Progress_Level_Upload = tk.Label(tab1, text = "Upload Progress").grid(row = 5, pady = 25)
Progress_Bar_Upload = Progressbar(tab1, length = 100, mode = "indeterminate")
Progress_Bar_Upload["value"] = 0
Progress_Bar_Upload.grid(column = 1, row = 5)

###Submit Button
Submit_Button_Upload = tk.Button(tab1, text = "Submit", command = Upload).grid(row = 6, column = 1)


###---------------------------------------------------------------------------------------------------------------------------------------------
###Download Function TAB2

###Information for user 
Text_Label_Download = tk.Label(tab2, text = "Welcome to TrueGeometry Download Function \n Get your Permanent API Key from Profile Page by \n Updagting your Profile @ www.truegeometry.com").grid(row = 0, column = 1, padx = 10, pady = 25)

### API Key Field
API_Key_Download = tk.StringVar() #Variable declaration to get API Key input
API_Key_Label_Download = tk.Label(tab2, text = "Enter API Key").grid(row = 1, padx = 10, pady = 25) 
API_Key_Entry_Download = tk.Entry(tab2, textvariable = API_Key_Download).grid(row = 1, column = 1)

###Enter Tags
API_FileName_Gui = tk.StringVar() #Variable declaration to get File Name
API_FileName_Lable = tk.Label(tab2, text = "Enter File Name").grid(row = 2, padx = 10, pady = 25)
API_FileName_Entry = tk.Entry(tab2, textvariable = API_FileName_Gui).grid(row = 2, column = 1)

###Progress Bar
Progress_Level_Download = tk.Label(tab2, text = "Download Progress").grid(row = 3, pady = 25)
Progress_Bar_Download = Progressbar(tab2, length = 100, mode = "determinate")
Progress_Bar_Download["value"] = 0
Progress_Bar_Download.grid(column = 1, row = 3)

###Submit Button
Submit_Button_Download = tk.Button(tab2, text = "Submit", command = Download).grid(row = 4, column = 1, pady = 25)


###---------------------------------------------------------------------------------------------------------------------------------------------
###Crossover Download Function TAB3

###Information for user 
Text_Label_Crossover = tk.Label(tab3, text = "Welcome to TrueGeometry Crossover Download \n Get your Permanent API Key from Profile Page by \n Updagting your Profile @ www.truegeometry.com").grid(row = 0, column = 1, padx = 10, pady = 25)

### API Key Field
API_Key_Crossover = tk.StringVar() #Variable declaration to get API Key input
API_Key_Label_Crossover = tk.Label(tab3, text = "Enter API Key").grid(row = 1, padx = 10, pady = 25) 
API_Key_Entry_Crossover = tk.Entry(tab3, textvariable = API_Key_Crossover).grid(row = 1, column = 1)

###Enter File Name
API_PrimaryName_Gui = tk.StringVar() #Variable declaration to get File Name
API_PrimaryName_Lable = tk.Label(tab3, text = "Enter Primary Part Name \n (Enter only the Numerals before \"-\")").grid(row = 2, padx = 10, pady = 25)
API_PrimaryName_Entry = tk.Entry(tab3, textvariable = API_PrimaryName_Gui).grid(row = 2, column = 1)

API_SecondaryName_Gui = tk.StringVar() #Variable declaration to get File Name
API_SecondaryName_Lable = tk.Label(tab3, text = "Enter Secondary Part Name \n (Enter only the Numerals before \"-\")").grid(row = 3, padx = 10, pady = 25)
API_SecondaryName_Entry = tk.Entry(tab3, textvariable = API_SecondaryName_Gui).grid(row = 3, column = 1)

###Progress Bar
Progress_Level_Crossover = tk.Label(tab3, text = "Download Progress").grid(row = 4, pady = 25)
Progress_Bar_Crossover = Progressbar(tab3, length = 100, mode = "determinate")
Progress_Bar_Crossover["value"] = 0
Progress_Bar_Crossover.grid(column = 1, row = 4)

###Submit Button
Submit_Button_Crossover = tk.Button(tab3, text = "Submit", command = Crossover).grid(row = 5, column = 1, pady = 25)


window.mainloop()
